module loopbackbasic {

  namespace "http://example.com/loopbackbasic";
  prefix loopbackbasic;

  import ietf-inet-types {
    prefix inet;
  }
  import tailf-ncs {
    prefix ncs;
  }

  description
    "Bla bla...";

  revision 2016-01-01 {
    description
      "Initial revision.";
  }

  augment /ncs:services {
    list loopbackbasic {
      key name;

      unique 'ip-address';
      unique 'device loopback-number';

      uses ncs:service-data;
      ncs:servicepoint "loopbackbasic-servicepoint";

      leaf name {
        type string;
      }

      leaf device {
        type leafref {
          path "/ncs:devices/ncs:device/ncs:name";
        }
      }

      leaf loopback-number {
        type int32;
      }

      leaf ip-address {
        type inet:ipv4-address;
      }
    }
  }
}
