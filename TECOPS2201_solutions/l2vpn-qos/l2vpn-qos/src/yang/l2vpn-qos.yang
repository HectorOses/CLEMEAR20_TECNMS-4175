module l2vpn-qos {

  namespace "http://example.com/l2vpn-qos";
  prefix l2vpn-qos;

  import ietf-inet-types {
    prefix inet;
  }
  import tailf-common {
    prefix tailf;
  }
  import tailf-ncs {
    prefix ncs;
  }

  description
    "NSO Training: l2vpn-qos";

  revision 2024-02-04 {
    description
      "Initial revision.";
  }

  list l2vpn-qos {
    description "This is an RFS skeleton service";

    key service-id;
    leaf service-id {
      tailf:info "Unique service id";
      tailf:cli-allow-range;
      type string;
    }

    uses ncs:service-data;
    ncs:servicepoint l2vpn-qos-servicepoint;

    leaf pseudowire-id {
      type uint32;
    }
    leaf vlan-id {
      type uint16 {
        range "1..4096";
      }
    }
    list pe-devices {
      min-elements 2;
      max-elements 2;
      key pe-device;

      leaf pe-device {
        type leafref {
          path "/ncs:devices/ncs:device/ncs:name";
        }
      }
      leaf pe-ce-interface-id {
        type string;
      }
    }
    leaf average-bit-rate {
      tailf:info "Target Bit Rate (bits per second)";
      mandatory true;
      type uint32 {
        range "8000..max";
      }
    }
    list ce-devices {
      min-elements 2;
      max-elements 2;
      key ce-device;
      tailf:info "device name";
      leaf ce-device {
        type leafref {
          path "/ncs:devices/ncs:device/ncs:name";
        }
      }
      leaf lan-ge-interface-id {
        type string;
      }
    }
  }
}
